submodule acidc-common {
    belongs-to acidc {
        prefix "acidc";
    }

    yang-version 1.1;

    import tailf-common {
        prefix tailf;
    }

    import tailf-ncs {
        prefix ncs;
    }

    import ietf-inet-types {
        prefix inet;
    }

    revision 2023-03-19 {
        description
          "Initial Revision.";
    }

    typedef percent {
        type decimal64 {
            fraction-digits 2;
            range "0 .. 100";
        }
    }

    typedef email {
        type string {
            pattern
              '[A-Z0-9._%+-]+@[A-Z0-9.-]+\.[A-Z]{2,}';
        }
    }
}
