submodule acidc-vrf-config {

    belongs-to acidc {
        prefix "acidc";
    }

    yang-version 1.1;

    import tailf-common {
        prefix tailf;
    }

    import tailf-ncs {
        prefix ncs;
    }

    include acidc-common {
        revision-date "2023-03-19";
    }

    revision 2023-03-19 {
        description
          "Initial Revision.";
    }

    grouping vrf-config-service {

        leaf name {
            tailf:info "Define VRF name";
            type dc-string;
        }

        leaf description {
            description
              "VRF Description";
            tailf:info "This description is auto-generated, use this field to overwrite the default behavior.";
            type string {
                length 1..128;
            }
        }

        leaf enforcement {
            tailf:info "Policy control enforcement preference ( enforced | unenforced )";
            tailf:cli-show-with-default;
            type vrf-enforcement;
            default enforced;
        }

        leaf vrf-type {
            description
              "vrf-type can be internet|private|isolated";
            type vrf-type;
            mandatory true;
        }
    }
}
