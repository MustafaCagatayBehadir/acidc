module acidc {

    yang-version 1.1;
    namespace "http://btsgrp.com/acidc";
    prefix acidc;

    import tailf-common {
        prefix tailf;
    }

    import tailf-ncs {
        prefix ncs;
    }

    include acidc-common {
        revision-date "2023-03-19";
    }

    description
      "ACI Scalability Package.";

    revision 2016-01-01 {
        description
          "Initial revision.";
    }

    list aci-site {
        description
          "This is an ACI Scalability Service Package.";

        key "fabric";

        leaf fabric {
            tailf:info "ACI fabric name";
            type leafref {
                path /ncs:devices/ncs:device/ncs:name;
            }
        }

        container aci-scalability {
            tailf:info "Define ACI fabric limits";

            leaf l3-context {
                tailf:info "VRF context limit for fabric.";
                type uint16;
                default 3000;
            }
        }

        container aci-alarm {
            tailf:info "Define ACI fabric alarm thresholds";

            leaf l3-context {
                tailf:info "VRF context alarm threshold for fabric.";
                type acidc:percent;
                default 80;
            }

            leaf email-address {
                tailf:info "Email address to be used, if the threshold value is exceeded.";
                type string;
            }

            leaf disable-alarm {
                tailf:info "To disable alarm notification.";
                type empty;
            }
        }

        container capacity-dashboard {
            description
              "ACI capacity dashboard.";
            config false;
            tailf:cdb-oper {
                tailf:persistent true;
            }

            leaf l3-context {
                description
                  "VRF usage ratio.";
                type acidc:percent;
            }
        }

        tailf:action CreateInfluxData {
            tailf:actionpoint AcidcCreateInfluxData;
            output {
                leaf result {
                    type string;
                }
                leaf message {
                    type string;
                }
            }
        }

        tailf:action CreatePostgresData {
            tailf:actionpoint AcidcCreatePostgresData;
            output {
                leaf result {
                    type string;
                }
                leaf message {
                    type string;
                }
            }
        }
    }
}
